MECViewRoadClearanceModule DEFINITIONS AUTOMATIC TAGS ::=
BEGIN
 
IMPORTS
    ReferencePoint, Header
FROM MECViewGeneralModule;

RoadClearanceEnvelope ::= SEQUENCE {
    version            INTEGER (0..MAX),
    server-id	       INTEGER (0..MAX),
    reference-point    ReferencePoint
}

Parameter ::= SEQUENCE {
	id			INTEGER (0..255),
	name		UTF8String,
	value		INTEGER (-10..10),
	position	ReferencePoint OPTIONAL
}

Parameters ::= SEQUENCE OF Parameter

RoadSection ::= SEQUENCE {
    geo-fence-id		INTEGER (0..255),
    parameters			Parameters
}

RoadSections ::= SEQUENCE OF RoadSection

RoadClearanceFrame ::= SEQUENCE {
    header              Header,
    envelope            RoadClearanceEnvelope,
    road-sections   	RoadSections
}

END
