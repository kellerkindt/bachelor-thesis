MECViewSensorModule DEFINITIONS AUTOMATIC TAGS ::=
BEGIN
 
IMPORTS
    ReferencePoint, PositionOffset, MovingVector, ObjectType, ObjectSize, Header
FROM MECViewGeneralModule;

SensorType ::= ENUMERATED {
    server,
    cam,
    lidar
}

SensorEnvelope ::= SEQUENCE {
    version            INTEGER (1..128),
    sensor-type        SensorType,
    sender-id          INTEGER (0..255),
    pole-id            INTEGER (0..31),
    reference-point    ReferencePoint,
    error-code         INTEGER (0..255)
}

SensorObjectDetection ::= SEQUENCE {
    local-id                    INTEGER (0..MAX),
    probability-of-existence    INTEGER (0..1000000),
    position-offset             PositionOffset,
    moving-vector               MovingVector OPTIONAL,
    type                        ObjectType,
    type-probability            INTEGER (0..1000000),
    size                        ObjectSize,
    orientation                 INTEGER (0..3600) OPTIONAL,
    std-dev-orientation         INTEGER (0..1800) OPTIONAL,
    measured                    BOOLEAN OPTIONAL
}

SensorObjectDetections ::= SEQUENCE OF SensorObjectDetection

SensorFrame ::= SEQUENCE {
    header              Header,
    envelope            SensorEnvelope,
    object-detections   SensorObjectDetections
}

SensorIdleFrame ::= SEQUENCE {
    version            INTEGER (1..128),
    sender-id          INTEGER (0..255),
    pole-id            INTEGER (0..31)
}

END
